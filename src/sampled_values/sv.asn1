IEC61850 DEFINITIONS ::= BEGIN
IMPORTS Data FROM ISO-IEC-9506-2
IEC 61850-9-2 Specific Protocol ::= CHOICE {
  savPdu [APPLICATION 0] IMPLICIT SavPdu,
}
  
  
SavPdu ::= SEQUENCE {
  noASDU [0] IMPLICIT INTEGER(1..65535),
  security [1] ANY OPTIONAL, 
  asdu [2] IMPLICIT SEQUENCE OF ASDU
}

ASDU ::= SEQUENCE {
  svID [0] IMPLICIT VisibleString, 
  datset [1] IMPLICIT VisibleString OPTIONAL, 
  smpCnt [2] IMPLICIT OCTET STRING (SIZE(2)),
  confRev [3] IMPLICIT OCTET STRING (SIZE(4)),
  refrTm [4] IMPLICIT UtcTime OPTIONAL, 
  smpSynch [5] IMPLICIT OCTET STRING (SIZE(1)), 
  smpRate [6] IMPLICIT OCTET STRING (SIZE(2)) OPTIONAL,
  sample [7] IMPLICIT OCTET STRING (SIZE(n)),
  smpMod [8] IMPLICIT OCTET STRING (SIZE(2)) OPTIONAL
}
